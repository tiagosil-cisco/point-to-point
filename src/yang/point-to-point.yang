module point-to-point {

  namespace "http://example.com/point-to-point";
  prefix point-to-point;

  import ietf-inet-types {
    prefix inet;
  }
  import tailf-common {
    prefix tailf;
  }
  import tailf-ncs {
    prefix ncs;
  }

  import ietf-yang-types {
    prefix yang;
  }



  description
    "Bla bla...";

  revision 2016-01-01 {
    description
      "Initial revision.";
  }

grouping ipv4_address {
  leaf ipv4-address {
      type inet:ipv4-address;
    }
    leaf mask {
      type inet:ipv4-address;
    }
}

grouping device_int_config {
  leaf device {
    type leafref {
      path "/ncs:devices/ncs:device/ncs:name";
    }
  }
  leaf interface_type {
    when "../device!=''";
    type interface_types;
    mandatory true;
  }
  leaf interface_id {
    when "../interface_type!=''";
    type string;
    mandatory true;
  }

  leaf encapsulation {
    type enumeration {
      enum "dot1q";
    }
  }

  leaf sub_interface_id {
    when "../encapsulation!=''";
    type uint16;
  }

  leaf vlan_id {
    when "../encapsulation!=''";
    type uint16;
  }
      

  leaf link_state {
    when "../interface_type!=''";
    type enumeration {
      enum "shutdown";
      enum "no shutdown";
    }
  }

}
typedef interface_types {
  type enumeration {
    enum GigabitEthernet;
    enum TenGigE;
    enum FortyGigE;
    enum HundredGigE;
  }
}



augment /ncs:services {
  list point-to-point {
    description "This is an RFS skeleton service";

key name;
      leaf name {
      tailf:info "Unique service id";
      type string;
    }

    uses ncs:service-data;
    ncs:servicepoint point-to-point-servicepoint;

    leaf bw {
      type enumeration {
        enum "1Gbps" {
          value "1000000";
        }
        enum "10Gbps" {
          value "10000000";
        }
        enum "40Gbps" {
          value "40000000";
        }
        
        enum "100Gbps"{
          value "100000000";
        }
      }
    }

    leaf cdp {
      type boolean;
    }

    leaf mtu {
      type int32;
    }

    leaf ipv4_enabled {
      type boolean;
    }

/*
    leaf ipv4_block {
      when "../ipv4_enabled='true'";
      type leafref {
        path "/resource-pools/ipalloc:ip-address-pool/ncs:name";
      }
      mandatory true;
    }
*/
    leaf ipv6_enabled {
      type boolean;
    }
/*
    leaf ipv6_block {
      when "../ipv6_enabled='true'";
      type leafref {
        path "/resource-pools/ipalloc:ip-address-pool/ncs:name";
      }
      mandatory true;
    }
*/
    container side_a {
      uses device_int_config;

      leaf vrf_a {
        when "../interface_type!=''";
        type string;
      }
    }

    container side_b {
      uses device_int_config;

      leaf vrf_b {
        when "../interface_type!=''";
        type string;
      }
    }


  }
}
}
